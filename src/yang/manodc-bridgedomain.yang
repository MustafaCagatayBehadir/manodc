submodule manodc-bridgedomain {

  belongs-to manodc {
    prefix "manodc";
  }

  yang-version 1.1;

  import ietf-inet-types {
    prefix inet;
  }

  import tailf-common {
    prefix tailf;
  }

  import tailf-ncs {
    prefix ncs;
  }

  import inventory-manager {
    prefix inv;
  }

  include manodc-types {
    revision-date "2024-08-22";
  }

  description
    "Turkcell MANO DC bridge-domain module.";

  revision 2024-08-22 {
    description
      "Initial revision.";
  }

  grouping bridge-domain-vlan {
    leaf site {
      tailf:info "Data center site name";
      type leafref {
        path "/inv:inventory-manager/inv:name";
      }
    }

    leaf name {
      tailf:info "Bridge domain name";
      type string;
    }

    leaf vlan {
      tailf:info "Vlan id";
      type vlan-id;
    }

    leaf description {
      tailf:info "Bridge domain vlan description";
      type string {
        pattern
          '[^\s]+' {
            error-message
              "No space/s allowed in vlan description";
          }
      }  
    }

    list switch {
      tailf:info "Vlan endpoint";
      key name;

      leaf name {
        tailf:info "Endpoint name";
        type leafref {
          path "/inv:inventory-manager[inv:name=current()/../../site]/inv:device/inv:name";
        }
      }

      list port {
        when "/inv:inventory-manager[inv:name=current()/../../site]/inv:device[inv:name=current()/../name]/inv:device-role = 'TOR'";
        tailf:info "Switch port";
        key id;
        leaf id {
          tailf:info "Port id";
          type string;

          // tailf:non-strict-leafref {
          //   path "/inv:inventory-manager[inv:name=current()/../../../site]/inv:device[inv:name=current()/../../name]/inv:interfaces/inv:interface/inv:id";
          // }
        }
        must "(count(/inv:inventory-manager[inv:name=current()/../../site]"+
          "/inv:device[inv:name=current()/../name]"+
          "/inv:interfaces/inv:interface[inv:id=current()/id])=1)" {
          error-message
            "Configuration not allowed: The specified port id does not exist in the device's inventory. Check the inventory-manager.";
        }
        must "(count(/manodc:bridge-domains/bridge-domain-vlan[manodc:site=current()/../../site]"+
          "[manodc:vlan != current()/../../vlan]"+
          "[manodc:name!=current()/../../name]"+
          "/switch[manodc:name= current()/../name]"+
          "/port[manodc:id = current()/id])=0)" {
          error-message
            "Configuration not allowed: When configuring multiple Bridge Domains on a port,"+ 
            "each Bridge Domain must use same Service Name across all ManoDC Services.";
        }
        must "(count(/manodc:bridge-domains/bridge-domain-vlan[manodc:site=current()/../../site]"+
          "[manodc:vlan != current()/../../vlan]"+
          "[manodc:name=current()/../../name]"+
          "/switch[manodc:name= current()/../name]"+
          "/port[manodc:id = current()/id]"+
          "/connected-host != current()/connected-host) = 0)"+
          "and (count(./host-port != current()/host-port) = 0)" {
          error-message
          "Configuration not allowed: When configuring multiple Bridge Domains on a port,"+ 
          "you must maintain same connected-host and connected-port definitions across all ManoDC Services.";
        }
        leaf connected-host {
          tailf:info "Connected host";
          type string;
          mandatory true;
        }

        leaf host-port {
          tailf:info "Host port";
          type string;
          mandatory true;
        }
        must "(count(/manodc:bridge-domains/bridge-domain-vlan[manodc:site=current()/../../site]"+
          "[manodc:vlan != current()/../../vlan]"+
          "[manodc:name=current()/../../name]"+
          "/switch[manodc:name= current()/../name]"+
          "/port[manodc:id = current()/id]"+
          "/mode = 'access' and current()/mode != 'access')=0)"+
          "or "+
          "(count(./mode = 'trunk' or .= 'native' and current()/mode = 'access') = 0)" {
          error-message
            "Configuration not allowed: When configuring multiple Bridge Domains on a port,"+ 
            "you must maintain consistent port-mode across all ManoDC Services.(Access VLAN and Trunk/Native VLAN cannot be configured on the same port)";
        }
        leaf mode {
          tailf:info "Port mode";
          type vlan-mode;
          default trunk;
        }

        leaf storm-control {
          when "../mode = 'access'";
          tailf:info "Enable storm control ";
          type boolean;
          default false;
        }
      }
    }

    container layer3 {
      presence
        "Enable layer 3 network configuration";
      tailf:info "Layer 3 network configuration";

      leaf vrf {
        tailf:info "VRF name";
        type string;
      }

      leaf gateway {
        tailf:info "SVI gateway";
        mandatory true;
        type tailf:ip-address-and-prefix-length;
        tailf:validate gateway-valpoint {
          tailf:dependency ".";
        }
      }
    }
  }

  grouping bridge-domain-vlan-data {
    leaf site {
      tailf:info "Data center site name";
      type string;
    }

    leaf name {
      tailf:info "Bridge domain name";
      type string;
    }

    leaf vlan {
      tailf:info "Vlan id";
      type uint16;
    }
  }

  grouping bridge-domain-vlan-switch-data {
    leaf site {
      tailf:info "Data center site name";
      type string;
    }

    leaf name {
      tailf:info "Bridge domain name";
      type string;
    }

    leaf vlan {
      tailf:info "Vlan id";
      type uint16;
    }

    leaf switch {
      tailf:info "Vlan endpoint";
      type string;
    }
  }

  grouping bridge-domain-vlan-switch {

    leaf site {
      tailf:info "Data center site name";
      type leafref {
        path "/inv:inventory-manager/inv:name";
      }
    }

    leaf name {
      tailf:info "Bridge domain name";
      type string;
    }

    leaf vlan {
      tailf:info "Vlan id";
      type vlan-id;
    }

    leaf switch {
      tailf:info "Vlan endpoint";
      type leafref {
        path "/ncs:devices/ncs:device/ncs:name";
      }
    }

    leaf description {
      tailf:info "Bridge domain vlan description";
      type string;
    }

    list port {
      tailf:info "Switch port";
      key id;

      leaf id {
        tailf:info "Port id";
        type tor-port;
      }

      leaf connected-host {
        tailf:info "Connected host";
        type string;
      }

      leaf host-port {
        tailf:info "Host port";
        type string;
      }

      leaf mode {
        tailf:info "Port mode";
        type vlan-mode;
        default trunk;
      }

      leaf storm-control {
        when "../mode = 'access'";
        tailf:info "Enable storm control ";
        type boolean;
        default false;
      }
    }

    container layer3 {
      presence
        "Enable layer 3 network configuration";
      tailf:info "Layer 3 network configuration";

      leaf vrf {
        tailf:info "VRF name";
        type string;
      }

      leaf address {
        tailf:info "SVI IP address";
        mandatory true;
        type tailf:ip-address-and-prefix-length;
      }

      leaf vip-address {
        tailf:info "Virtual IP address";
        type tailf:ip-address-and-prefix-length;
      }

      leaf vrrpv3-id {
        tailf:info "VRRP group id";
        type uint8;
      }

      leaf vrrpv3-priority {
        tailf:info "VRRP priority";
        type uint8;
      }
    }
  }
}
