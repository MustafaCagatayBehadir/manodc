submodule manodc-nano-services {

  belongs-to manodc {
    prefix "manodc";
  }

  yang-version 1.1;

  import tailf-common {
    prefix tailf;
  }
  import tailf-ncs {
    prefix ncs;
  }

  description
    "Mano data-center nano service.";

  revision 2024-08-22 {
    description
      "Initial revision.";
  }

  identity vlan-endpoint {
    base ncs:plan-component-type;
  }

  identity id-allocated {
    base ncs:plan-state;
  }

  identity vlan-configured {
    base ncs:plan-state;
  }

  identity vlan-switch-configured {
    base ncs:plan-state;
  }

  ncs:plan-outline bridge-domain-vlan-nano-plan {
    description
      "Manodc vlan service plan.";

    ncs:self-as-service-status;

    ncs:component-type "ncs:self" {
      ncs:state "ncs:init";

      ncs:state "manodc:id-allocated" {
        ncs:create {
          ncs:nano-callback;
        }
      }

      ncs:state "ncs:ready";
    }

    ncs:component-type "manodc:vlan-endpoint" {
      ncs:state "ncs:init" {
        ncs:delete {
          ncs:pre-condition {
            ncs:monitor "/manodc:dc-sites/manodc:dc-site[manodc:fabric='AVR-NDC1']/manodc:bridge-domains/manodc:bridge-domain-vlan-switch[manodc:name=$BD_NAME][manodc:vlan=$VLAN][manodc:switch=$SWITCH]" {
              ncs:trigger-on-delete;
            }
          }
        }
      }

      ncs:state "manodc:vlan-configured" {
        ncs:create {
          ncs:pre-condition {
            ncs:monitor  "$SERVICE/plan/component[type='ncs:self'][name='self']/state[name='manodc:id-allocated']" {
              ncs:trigger-expr "status = 'reached'";
            }
          }
          ncs:nano-callback;
        }
      }

      ncs:state "ncs:ready";
    }
  }

  ncs:service-behavior-tree bridge-domain-vlan-servicepoint {
    description
      "Vlan service behavior tree.";
    ncs:plan-outline-ref "bridge-domain-vlan-nano-plan";
    ncs:plan-location "/manodc:dc-sites/manodc:dc-site/manodc:bridge-domains/manodc:bridge-domain-vlan-data";
    ncs:selector {
      ncs:create-component "'self'" {
        ncs:component-type-ref "ncs:self";
      }

      ncs:variable "BD_NAME" {
        ncs:value-expr "name";
      }

      ncs:variable "VLAN" {
        ncs:value-expr "vlan";
      }

      ncs:variable "FABRIC" {
        ncs:value-expr "../../../fabric";
      }

      ncs:multiplier {
        ncs:foreach "switch" {
          ncs:variable "SWITCH" {
            ncs:value-expr "name";
          }
          ncs:create-component "name" {
            ncs:component-type-ref "manodc:vlan-endpoint";
          }
        }
      }
    }
  }

  ncs:plan-outline bridge-domain-vlan-switch-nano-plan {
    description
      "Manodc vlan switch service plan.";

    ncs:component-type "ncs:self" {
      ncs:state "ncs:init";

      ncs:state "manodc:vlan-switch-configured" {
        ncs:create {
          ncs:nano-callback;
        }
      }

      ncs:state "ncs:ready";
    }
  }

  ncs:service-behavior-tree bridge-domain-vlan-switch-servicepoint {
    ncs:converge-on-re-deploy;
    ncs:plan-outline-ref "bridge-domain-vlan-switch-nano-plan";
    ncs:plan-location "/manodc:dc-sites/manodc:dc-site/manodc:bridge-domains/manodc:bridge-domain-vlan-switch-data";
    ncs:selector {
      ncs:create-component "'self'" {
        ncs:component-type-ref "ncs:self";
      }
    }
  }
}
