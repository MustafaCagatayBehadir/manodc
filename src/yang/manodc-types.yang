submodule manodc-types {
  belongs-to manodc {
    prefix "manodc";
  }

  yang-version 1.1;

  import tailf-common {
    prefix tailf;
  }
  import tailf-ncs {
    prefix ncs;
  }

  description
    "Turkcell MANO DC common types module.";

  revision 2024-08-22 {
    description
      "Initial revision.";
  }

  identity switch {
    base ncs:plan-component-type;
  }

  identity configured {
    base ncs:plan-state;
  }

  typedef switch-type {
    type enumeration {
      enum eor {
        value 1;
      }
      enum tor {
        value 2;
      }
    }
  }

  typedef eor-role {
    type enumeration {
      enum primary {
        value 1;
      }
      enum secondary {
        value 2;
      }
    }
  }

  typedef tor-port {
    type string {
      pattern
        '[1-9]/[1-9][0-9]{0,1}';
    }
  }

  typedef vlan-id {
    type uint16 {
      range "1..4094";
    }
  }

  typedef vlan-mode {
    type enumeration {
      enum trunk {
        value 1;
      }
      enum access {
        value 2;
      }
      enum native {
        value 3;
      }
    }
  }

  typedef validation-state {
    type enumeration {
      enum enable {
        value 1;
      }
      enum disable {
        value 2;
      }
    }
  }

  typedef action-data-source {
    type enumeration {
      enum portal {
        value 1;
      }
      enum csv {
        value 2;
      }
    }
  }

  typedef uuid {
    type string {
      pattern
        '[0-9a-fA-F]{8}-[0-9a-fA-F]{4}-[0-9a-fA-F]{4}-'
      + '[0-9a-fA-F]{4}-[0-9a-fA-F]{12}';
    }
    description
      "A Universally Unique IDentifier in the string representation
       defined in RFC 4122.  The canonical representation uses
       lowercase characters.

       The following is an example of a UUID in string representation:
       f81d4fae-7dec-11d0-a765-00a0c91e6bf6
      ";
    reference
      "RFC 4122: A Universally Unique IDentifier (UUID) URN
                 Namespace";
  }
}
